# Specification: Specification Document
- Description: Requirements Document

## smt_m: Model Requirements (Requirement Type)

### smt_m_001: Model effects (Requirement Type)
The model shall contain typical sensor effects, which are a result of the signal propagation and the signal processing until the desired output interface.
- Source: Internal
- Testcase: Expert review
- Author: LE
- Status: Pending

### smt_m_001_001: Azimuth field of view (Requirement Type)
Objects shall only be detected inside an azimuth field of view of +- 30°.
- Source: Internal
- Testcase: Unit tests
  Verification tests
- Author: CL
- Status: Pending

### smt_m_001_002: Maximum range (Requirement Type)
Objects shall only be detected to a maximum detection range of 1.1 times the nominal range.
- Source: Internal
- Author: CL
- Status: Pending
- Testcase: Unit tests
  Verification tests

## smt_p: Parameter Requirements (Requirement Type)

### smt_p_001: FMI Parameters (Requirement Type)
The sensor model shall be customizable via FMI parameters.
- Testcase: Check modelDescription
- Author: CL
- Status: Pending

### smt_p_002: Parameters (Requirement Type)
The sensor model shall have the following parameters:
- Nominal Range in m
- Source: Internal
- Testcase: Check modelDescription
- Author: CL
- Status: Pending

## smt_se: Simulation Environment Requirements (Requirement Type)

### smt_se_001: Ubuntu 22.04 (Requirement Type)
The source code has to be buildable and run on Ubuntu 22.04.
- Source: Internal
- Testcase: Successful build process in pipeline
- Status: Pending
- Author: LE

## smt_si: Simulation Integration Requirements (Requirement Type)

### smt_si_001: FMU packaging (Requirement Type)
The sensor model has to be packaged as an FMU.
- Source: Internal
- Author: CL
- Status: Pending
- Testcase: FMU Compliance Check

### smt_si_002: Input interface (Requirement Type)
The provided input interface is OSI SensorView version 3.7.0.
- Source: Internal
- Testcase: Check modelDescription
- Author: CL
- Status: Pending

### smt_si_003: Input OSI fields (Requirement Type)
The sensor model shall only require the following OSI fields:
- SensorView
    - timestamp
    - mounting_position
    - sensor_id
    - global_ground_truth (GroundTruth)
        - host_vehicle_id
        - moving_object (MovingObject)
            - id
            - base (BaseMoving)
                - orientation (Orientation3d)
                - position (Vector3d)
                - dimension (Dimension3d)
- Author: LE
- Status: Pending
- Source: Internal
- Testcase: Evaluate model output when only providing this input.
- links to -> R39

### smt_si_004: Output interface (Requirement Type)
The provided output interface is OSI SensorData version 3.7.0.
- Source: Internal
- Testcase: Check modelDescription
- Author: CL
- Status: Pending

### smt_si_005: Output OSI fields (Requirement Type)
The following OSI fields has to be filled by the sensor model:
- SensorData
    - timestamp
    - moving_object (MovingObject)
        - header
            - ground_truth_id
            - tracking_id
            - existance_probability
            - measurement_state
            - sensor_id
        - base (BaseMoving)
            - orientation (Orientation3d)
            - position (Vector3d)
            - dimension (Dimension3d)
- Source: Internal
- Testcase: OSI Validation
- Author: LE
- Status: Pending

## pr_001: Phenomenological Radar RQ List (Requirement Type)

## pr_002: Requirement Phase (Requirement Type)

## pr_0: Design Specification (Requirement Type)

## pr_0: Implementation/Integration (Requirement Type)

## pr_0: Evaluation (Requirement Type)

## pr_0 11: FMU model (Requirement Type)
The model has to be delivered as a FMU compliant model.
- Source: Offer to customer
- Testcase: FMU checker
- Author: LE
- CL: CL1
- Status: Pending

## pr_002: Execution speed (Requirement Type)
The sensor model shall execute in realtime at 10 Hz with 10 ground truth moving objects on a sota laptop.
- Source: Internal
- Testcase: Example
- Author: LE
- Status: Pending
- CL: CL2

## smt_002: Code documentation (Requirement Type)
All functions and member variables have to be documented in javadoc format.
- Source: Internal
- Testcase: Doxygen check
- Author: LE
- Status: Pending

## pr_005: Build Windows (Requirement Type)
The source code has to be buildable on a Windows 11.
- Testcase: Successful build process in Git pipeline
- Source: Internal
- Author: LE
- Status: Pending

## pr_006: Model input (Requirement Type)
The model calculations shall only be based on OSI ground truth stationary and moving objects.
- Source: Internal
- Testcase: Evaluate model output when only providing object input.
- Author: CL
- Status: Pending

## pr_002_008 (Requirement Type)

## pr_002_008: Output interface (Requirement Type)
The provided output interface is an OSI with version 3.7.0.
- Source: Internal
- Testcase: Version Check OSI
- CL: CL1
- Author: LE
- Status: Pending
- Comment: LE: Clarify with customer OSI version

## pr_002_008_1: Output OSI fields (Requirement Type)
- RadarDetectionData
     - detection
          - position (Spherical3d)
          - radial_velocity
          - rcs
- Comment: LE: Clarify with customer, which output interfaces are necessary.
- Status: Pending
- Author: LE
- CL: CL1
- Source: Offer to customer
- Testcase: Output OSI check

## pr_009: Parametrised model (Requirement Type)
The model can be parametrised via FMI parameters.
- Source: Costumer
- Testcase: Test FMI model parameters
- CL: CL2
- Author: LE
- Status: Pending

## pr_009_001: Parametrised model no FMU (Requirement Type)
If the model is used as a standalone library, the parameters defined within the model shall be used.
- Source: Costumer
- Testcase: Test model parameters as standalone without FMI parameter
- CL: CL2
- Author: LE
- Status: Pending

## pr_009_002: Parameter model (Requirement Type)
The following parameters shall be adjustable within the model:
- max elevation (Effect: antenna diagram)
- min elevation (Effect: antenna diagram)
- max azimuth (Effect: antenna diagram)
- min azimuth (Effect: antenna diagram)
- max velocity (Effect: FFT-processing of received signal velocity dimension)
- min velocity (Effect: FFT-processing of received signal velocity dimension)
- min range (Effect: Power reduction Low-Passfilter)
- max range (Effect: FFT processing)
- number bins elevation (Effect: FFT processing elevation dimension + antenna layout)
- number bins azimuth (Effect: FFT processing azimuth dimension + antenna layout)
- number bins velocity (Effect: FFT processing velocity dimension)
- number bins range (Effect: FFT processing range dimension)
- margin range (Effect: High reflecting targets)
- margin FOV (Effect: High reflecting targets)
- maximum number detection per spherical bin (Effect: Doppler dimension in FFT prorcessing)
- RCS standard deviation (Effect: Power fluctuations due to signal processing and signal propagation and HF components)
- Status: Pending
- Author: LE
- Testcase: Expert review
- CL: CL1, CL2, CL3
- Source: Internal

## pr_010_003: Maximum range (Requirement Type)
The model shall include ambiguities in the angle dimension due to the FFT processing.
- Source: Internal
- Author: LE
- Status: Pending
- Testcase: Unit tests
  Verification tests
- CL: CL2, CL3

## pr_010_004: Velocity ambiguities (Requirement Type)
The model shall include ambiguities in the velocity dimension due to the FFT processing.
- Source: Internal
- Author: LE
- Status: Pending
- Testcase: Unit tests
  Verification tests
- CL: CL2, CL3

## pr_010_006: Min range (Requirement Type)
The model shall include a minimum range due to the power filtering.
- Source: Internal
- Author: LE
- Status: Pending
- Testcase: Unit tests
  Verification tests
- CL: CL2, CL3

## pr_010_007: Occlusion (Requirement Type)
The model shall include occlusion of other object due to stationary objects.
- Source: Internal
- Author: LE
- Status: Pending
- Testcase: Unit tests
  Verification tests
- CL: CL2, CL3

## pr_010_005: Multipath propagation road and objects (Requirement Type)
The model shall include detections on moving objects, which are occluded by other moving objects.
- Source: Internal
- Author: LE
- Status: Pending
- Testcase: Unit tests
  Verification tests
- CL: CL2, CL3

## pr_010_008: RCS characteristic (Requirement Type)
The modell shall output angle depent RCS values for stationary and moving objects of the specified types.
- Source: Internal
- Testcase: Unit tests
  Verification tests
- Author: LE
- Status: Pending
- CL: CL2, CL3

## pr_010_009: Number detections on object (Requirement Type)
The model shall generate at least 5 detections per object of type car.
- Source: Information of Valeo
- Author: LE
- Status: Pending
- Comment: LE: Is effect necessary?
- Testcase: Unit tests
  Verification tests
- CL: CL2, CL3

## pr_010_010: Maximum number detections (Requirement Type)
The model shall output per cycle a maximum number of XX detections.
- Source: Internal
- Author: LE
- Status: Pending
- Comment: LE: Is effect necessary?
- Testcase: Unit tests
  Verification tests
- CL: CL2, CL3

## pr_010_011: Antenna diagram maximum detectable RCS (Requirement Type)
The modell shall ignore detections, which are outside the FOV and under a defined RCS value.
- Source: Internal
- Author: LE
- Status: Pending
- Comment: LE: Is effect necessary?
- Testcase: Unit tests
  Verification tests
- CL: CL2, CL3

## pr_010_012: Road clutter (Requirement Type)
The modell shall output detections due to road reflections in the sensor vicinity.
- Source: Internal
- Author: LE
- Status: Pending
- Comment: LE: Is effect necessary?
- Testcase: Unit tests
  Verification tests
- CL: CL2, CL3

## pr_010_013: Vegetation clutter (Requirement Type)
The modell shall output detections due to vegetation.
- Source: Internal
- Author: LE
- Status: Pending
- Comment: LE: Is effect necessary?
- Testcase: Unit tests
  Verification tests
- CL: CL2, CL3

## pr_002_008 (Requirement Type)

## R38

## R39
- links to -> R39

## R42
